module sonic-acl {
	namespace "http://github.com/Azure/sonic-acl";
	prefix acl;
	yang-version 1.1;

	import ietf-inet-types {
		prefix inet;
	}

	import sonic-port {
		prefix prt;
	}

	organization
		"SONiC";

	contact
		"SONiC";

	description
		"SONIC ACL";

	revision 2019-05-15 {
		description
			"Initial revision.";
	}

	container sonic-acl {

		container ACL_TABLE {

			list ACL_TABLE_LIST {
				key "aclname";

				leaf aclname {
					type string {
						pattern '[a-zA-Z0-9]{1}([-a-zA-Z0-9_]{1,63})' {
							error-app-tag aclname-invalid;
						}
					}
				}

				leaf policy_desc {
					type string {
						length 1..255 {
							error-app-tag policy-desc-invalid-length;
						}
					}
				}

				leaf stage {
					type enumeration {
						enum INGRESS;
						enum EGRESS;
					}
				}

				leaf type {
					type enumeration {
						enum MIRROR;
						enum MIRRORV6;
						enum L3;
						enum L3V6;
					}
				}

				leaf-list ports {
					type leafref {
						path "/prt:sonic-port/prt:PORT/prt:PORT_LIST/prt:ifname";
					}
				}
			}
		}

		container ACL_RULE {

			list ACL_RULE_LIST { 
				key "aclname rulename";

				leaf aclname {
					type leafref {
						path "../../../ACL_TABLE/ACL_TABLE_LIST/aclname";
					}
				} 

				leaf rulename {
					type string {
						pattern '[a-zA-Z0-9]{1}([-a-zA-Z0-9_]{1,63})' {
							error-app-tag rulename-invalid;
						}
					}
				}

				leaf PRIORITY {
					type uint16 {
						range "1..65535"{
							error-app-tag priority-invalid-range;
							error-message "Invalid ACL rule priority.";
						}
					}
				}

				leaf RULE_DESCRIPTION {
					type string {
						length 1..255 {
							error-app-tag ruledesc-invalid-length;
						}
					}
				}

				leaf PACKET_ACTION {
					mandatory true;
					type enumeration {
						enum FORWARD;
						enum DROP;
						enum REDIRECT;
					}
				}

				leaf IP_TYPE {
					//mandatory true;
					type enumeration {
						enum ANY;
						enum IP;
						enum IPV4;
						enum IPV4ANY;
						enum NON_IPV4;
						enum IPV6ANY;
						enum NON_IPV6;
					}
				}

				leaf IP_PROTOCOL {
					type uint8 {
						range "1|2|6|17|46|47|51|103|115";
					}
				}

				leaf ETHER_TYPE {
					type string {
						pattern "(0x88CC)|(0x8100)|(0x8915)|(0x0806)|(0x0800)|(0x86DD)|(0x8847)" {
							error-message "Invalid ACL Rule Ether Type";
							error-app-tag ether-type-invalid;
						}
					}
				}

				choice ip_src_dst {
					case ipv4_src_dst {
						when "boolean(IP_TYPE[.='ANY' or .='IP' or .='IPV4' or .='IPV4ANY'])";
						leaf SRC_IP {
							mandatory true;
							type inet:ipv4-prefix;
						}
						leaf DST_IP {
							mandatory true;
							type inet:ipv4-prefix;
						}
					}
					case ipv6_src_dst {
						when "boolean(IP_TYPE[.='ANY' or .='IP' or .='IPV6' or .='IPV6ANY'])";
						leaf SRC_IPV6 {
							mandatory true;
							type inet:ipv6-prefix;    
						}
						leaf DST_IPV6 {
							mandatory true;
							type inet:ipv6-prefix;    
						}
					}
				}

				choice src_port {
					case l4_src_port {
						leaf L4_SRC_PORT {
							type inet:port-number;
						}
					}
					case l4_src_port_range {
						leaf L4_SRC_PORT_RANGE {
							type string {
								pattern "[0-9]{1,5}(-)[0-9]{1,5}" {
									error-app-tag src-port-range-invalid;
								}
							}
						}
					}
				}

				choice dst_port {
					case l4_dst_port {
						leaf L4_DST_PORT {
							type inet:port-number;
						}
					}
					case l4_dst_port_range {
						leaf L4_DST_PORT_RANGE {
							type string {
								pattern "[0-9]{1,5}(-)[0-9]{1,5}" {
									error-app-tag dst-port-range-invalid;
								}
							}
						}
					}
				}

				leaf TCP_FLAGS { 
					type string {
						pattern "0[xX][0-9a-fA-F]{2}[/]0[xX][0-9a-fA-F]{2}" {
							error-app-tag tcp-flag-invalid;
						}
					}
				}

				leaf DSCP { 
					type inet:dscp;
				}
			}
		}
	}
}
